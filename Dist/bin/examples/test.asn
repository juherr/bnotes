-- test.asn --

TEST_ASN

DEFINITIONS IMPLICIT TAGS ::= BEGIN

EXPORTS TestOCT,TestPRN,TestI32,TestI16,TestI8,ContentType,ValueWithParams,ParamsMap,ContentPartHeaders,ContentPartHeader,ContentSchema,Data,DataArray;
	-- --

	TestIR  ::= INTEGER (1 .. 5)
	TestI8	::= INTEGER (0 .. 255)
	TestI14 ::= INTEGER (0 .. 16384)
	TestI16	::= INTEGER (0 .. 65535)
	TestI32	::= INTEGER (0 .. 4294967295)	
	TestI	::= INTEGER
	TestNI  ::= INTEGER (-128 .. 128)
	TestNI2  ::= INTEGER (-2048 .. 2048)

	TestPRN	::= PrintableString
	TestOCT	::= OCTET STRING

	
	Data   ::= CHOICE {
		plain 		[0] TestPRN, 
		unicode		[1] TestOCT, 
		binary		[2] TestOCT,
		simpleType	[3] PrintableString,
		simpleOctType	[4] OCTET STRING,
		booleanType	[5] BOOLEAN,
		intType		[6] INTEGER,
		intBndType	[7] INTEGER (0 .. 255)		
	}

	DataArray ::= SEQUENCE OF Data

	DataSeq   ::= SEQUENCE {
		plain 		[0] TestPRN, 
		unicode		[1] TestOCT OPTIONAL, 
		binary		[2] TestOCT,
		simpleType	[3] PrintableString,
		simpleOctType   OCTET STRING,
		booleanType	[5] BOOLEAN,
		intType		[6] INTEGER,
		intBndType	[7] INTEGER (0 .. 255),
		stringArray	[8] SEQUENCE OF PrintableString,
		dataArray	[9] SEQUENCE OF Data,
		extension	ANY OPTIONAL
	}	

	DataSeqMO ::= SEQUENCE {
		plain 		[0] TestPRN, 
		unicode		[1] TestOCT OPTIONAL, 
		binary		[2] TestOCT OPTIONAL,
		simpleType	[3] PrintableString OPTIONAL,
		simpleOctType   OCTET STRING,
		booleanType	[5] BOOLEAN OPTIONAL,
		intType		[6] INTEGER OPTIONAL,
		intBndType	[7] INTEGER (0 .. 255) OPTIONAL,
		stringArray	[8] SEQUENCE OF PrintableString OPTIONAL,
		dataArray	[9] SEQUENCE OF Data OPTIONAL,
		plain2 		[10] TestPRN OPTIONAL, 
		unicode2	[18] TestOCT OPTIONAL, 
		binary2		[11] TestOCT OPTIONAL,
		simpleType2	[12] PrintableString OPTIONAL,
		simpleOctType2   OCTET STRING OPTIONAL,
		booleanType2	[13] BOOLEAN OPTIONAL,
		intType2	[19] INTEGER OPTIONAL,
		intBndType2	[14] INTEGER (0 .. 255) OPTIONAL,
		stringArray2	[15] SEQUENCE OF PrintableString OPTIONAL,
		dataArray2	[16] SEQUENCE OF Data OPTIONAL,
		plain3 		[17] TestPRN OPTIONAL
	}


	DataSeqArray ::= SEQUENCE OF DataSeq
	StringArray ::= SEQUENCE OF PrintableString
	UTF8StringArray ::= SEQUENCE OF UTF8String
	OctetStringArray ::= SEQUENCE OF OCTET STRING

	ITUType1 ::= VisibleString
	ITUType2 ::= [APPLICATION 3] IMPLICIT ITUType1
	ITUType3 ::= [2] ITUType2
	ITUType4 ::= [APPLICATION 7] IMPLICIT ITUType3
	ITUType5 ::= [2] IMPLICIT ITUType2	
	ITUType6 ::= [9] VisibleString

	ITUSequence ::= SEQUENCE {
		type1  VisibleString,
		type2  [APPLICATION 3] IMPLICIT ITUType1,
		type3  [2] ITUType2,
		type4  [APPLICATION 7] IMPLICIT ITUType3,
		type5  [2] IMPLICIT ITUType2 OPTIONAL,
		type6  [7] VisibleString,
		type7  [8] ITUType6
	}

	NullSequence ::= NULL
	TaggedNullSequence ::= [1] NULL

	SequenceWithNull ::= SEQUENCE {
		test	PrintableString,
		nullVal	NULL,
		test2	[1] PrintableString
	}


	TaggedSequence ::= [APPLICATION 8] SEQUENCE {
		type1  [7] VisibleString OPTIONAL
	}


	ValueWithParams ::= SEQUENCE
	{
		value		[0]	PrintableString,			-- Значение
		params		[1]	SEQUENCE OF PlainParamsMap OPTIONAL	-- Текстовые параметры
	}

	PlainParamsMap ::= SEQUENCE
	{
		param_name	[1]	PrintableString,
		param_value	[2]	PrintableString
	}

	ContentPartHeader ::= SEQUENCE
	{
		name		[0]	PrintableString,		
		values		[1]	SEQUENCE OF ValueWithParams
	}

	ContentPartHeaders ::= SEQUENCE OF ContentPartHeader

	-- * Тип контента * --
	ContentType ::= ENUMERATED {
		text_any						(100),
		text_html						(101),
		text_plain						(102),
		audio_x_midi						(306), -- extension *.mid;*.midi
		video_any						(400),
		video_mpeg						(401), -- extension *.mpg;*.mpeg
		video_avi						(402), -- extension *.avi
		video_quicktime						(403), -- extension *.qt;*.mov
		video_x_msvideo						(404), -- extension *.avi
		application_smil					(500)  -- SMIL
	}

	ContentSchema ::= ENUMERATED {
		multipart_any						(110),
		multipart_mixed						(111),
		multipart_form_data					(112),
		multipart_byteranges					(113),
		multipart_alternative					(114),
		multipart_related					(175)		
	}

	SequenceWithEnum ::= SEQUENCE {
		item		PrintableString,
		enval		ContentSchema,
		taggedEnval	[1] ContentSchema
	}
	
	TestRecursiveDefinetion ::= SEQUENCE
	{
		name			[1]	PrintableString,
		value			[2]	TestRecursiveDefinetion OPTIONAL
	}

	SequenceWithDefault ::= SEQUENCE {
		nodefault		[0] INTEGER,
		withDefault		[1] PrintableString DEFAULT "dd",
		withIntDef 		[2] INTEGER DEFAULT 120,
		withSeqDef		[3] SEQUENCE {
			name	PrintableString,
			email	PrintableString
		}
		DEFAULT { name "Name", email "Email"},
		withOctDef		[4] TestOCT DEFAULT '01101100'B,
		withOctDef2		[5] OCTET STRING DEFAULT 'FFEEAA'H,
		withSeqOf		[6] SEQUENCE OF PrintableString DEFAULT { "aa","dd" },
		withSeqOf2		[7] SEQUENCE OF TestPRN DEFAULT { "cc","ee" },
		withSeqOf3		[8] StringArray DEFAULT { "fff","ggg" }
	}

	SetWithDefault ::= SET {
		nodefault		[2] INTEGER,
		nodefault2		[1] TestPRN,
		default3		[3] PrintableString DEFAULT "DDDdd"
	}

	TestSequenceWithNonames ::= SEQUENCE {
		seq	[0] SEQUENCE {
			it1 INTEGER OPTIONAL
		},
		ch	[1] CHOICE {
			it1 [0] INTEGER,
			it2 [1] OCTET STRING
		},
		seqf	[2] SEQUENCE OF SEQUENCE {
			it1 INTEGER OPTIONAL
		}
	}


	SetOfTest	::= SET OF Data

	TestBitStr	::= BIT STRING

	TestBitStrBnd	::= BIT STRING(SIZE(1..16))

	TestUnicodeStr	::= UTF8String

	TestUnicodeStrBnd ::= UTF8String(SIZE(12))

	TestSequenceV12 ::= SEQUENCE {
		attrSimple	[0] PrintableString,
		attrStr		[1] PrintableString (SIZE(1..4)),
		attrStr2	[2] TestPRN,
		attrArr		[3] SEQUENCE SIZE(1..5) OF PrintableString,
		attrBitStr	[4] BIT STRING OPTIONAL,
		attrBitStrDef	[4] BIT STRING DEFAULT '011'B,
		attrBitStrBnd	[5] BIT STRING(SIZE(1..36)) OPTIONAL,
		attrBoxBitStr	[6] TestBitStrBnd OPTIONAL,
		attrStrict	[7] OCTET STRING(SIZE(4))
	}

    	BugPrimitive ::= CHOICE
    	{
      		bugBoolean [0] BOOLEAN,
      		bugInteger [1] INTEGER
    	}

    	BugEnum ::= INTEGER

    	BugSequenceType ::= SEQUENCE
    	{
      		booleanField [0] BOOLEAN,
      		integerField [0] INTEGER
    	}

    	BugValueType ::= CHOICE
    	{
      		bugPrimitive [0] BugPrimitive,
      		bugEnum      [1] BugEnum,
      		bugSequence  [2] BugSequenceType
    	}

    	BugList ::= SEQUENCE OF BugValueType

	TaggedSeqInSeq ::= [APPLICATION 4] SEQUENCE 
	{
		field [0] PlainParamsMap
	}

	TestReal ::= REAL

	TestGT ::= GeneralizedTime

	TestUTC ::= UTCTime

	TestLong ::= INTEGER(1 .. 2247483648)


	TestSeqV13 ::= SEQUENCE 
	{
		field1 [0] REAL,
		fieldI INTEGER,
		field2 TestReal,
		field3 REAL OPTIONAL,
		field4 [1] REAL,
		field5 GeneralizedTime,
		field6 UTCTime,
		field7 TestLong
	}

	TestLongTag ::= [APPLICATION 15123] INTEGER
	Test128Tag ::= [APPLICATION 128] INTEGER

	TestSimpleSequence ::= SEQUENCE
	{
		field1 [0] INTEGER,
		field2 [1] UTF8String,
		field3 [2] UTF8String
	}

	TestLongTag2 ::= CHOICE {
		testa [33] TestLongTag2Choice
	}

	TestLongTag2Choice ::= SEQUENCE {
		testb [0] INTEGER
	}

	field3Default UTF8String ::= "Sssdsd"

	TestParent ::= SEQUENCE {
		field1	[0] INTEGER,
		field2	[1] OCTET STRING OPTIONAL,
		field3	[2] UTF8String DEFAULT field3Default,
		field4	[3] INTEGER
	}

	TestTParent ::= TestParent

	TestChild3 ::= SEQUENCE {
		COMPONENTS OF TestTParent,
		field5	[4] UTF8String,
		COMPONENTS OF SEQUENCE {
			field6 [5] INTEGER DEFAULT 0
		}
	}

	TestParent2 ::= CHOICE {
		field10	[0] INTEGER,
		field20	[1] OCTET STRING OPTIONAL,
		field30	[2] UTF8String,
		field40	[3] INTEGER
	}

	TestTParent2 ::= TestParent2

	TestChild2 ::= CHOICE {
		COMPONENTS OF TestTParent2,
		field5	[4] UTF8String,
		COMPONENTS OF CHOICE {
			field6 [7] UTF8String
		}
	}

	TestOID ::= OBJECT IDENTIFIER

	TestSeqOID ::= SEQUENCE {
		field1	[0] OBJECT IDENTIFIER,
		field2	[1] OBJECT IDENTIFIER OPTIONAL,
		field3	[2] INTEGER
	}

	FQDN ::= VisibleString(
		FROM ( "a".."z" | "A".."Z" |"0".."9"| ".-" )
		
	)
	( SIZE (1..255) )

	Minor ::= [APPLICATION 105] IMPLICIT INTEGER
	Major ::= [APPLICATION 106] IMPLICIT INTEGER

	Version ::= [APPLICATION 74] IMPLICIT SET {
		minor Minor OPTIONAL,
		major Major OPTIONAL
	}

	LstVersion ::= [APPLICATION 75] IMPLICIT SET OF Version

	Config ::=  [APPLICATION 76] IMPLICIT SEQUENCE {
		lstVersion LstVersion,
		major_config Major
	}

	Config2 ::=  [APPLICATION 79] IMPLICIT SEQUENCE {
		lstVersion LstVersion,
		major_config Major
	}

	TestTaggedSetInSet ::= [APPLICATION 77] IMPLICIT SET { 
		config1 Config, 
		config2 Config2
	} 

	Set1 ::= [APPLICATION 55] IMPLICIT SET { 
		set1ID INTEGER 
	}
	
	Set2 ::= [APPLICATION 128] IMPLICIT SET OF Set1
	
	Set3 ::= [APPLICATION 124] IMPLICIT SET{ 
		set2 Set2
	}
	
	Set4 ::= [APPLICATION 61] IMPLICIT SET OF Set3

	Set5 ::= [APPLICATION 127] IMPLICIT SET OF Set3

	Set6 ::= [APPLICATION 56] IMPLICIT SET {
		set4 Set4,
		set5 Set5
	}

	Set7 ::= [APPLICATION 90] IMPLICIT SET {
		set6 Set6
	}

	BBSQ ::= SEQUENCE SIZE (1..1000) OF TestSeqV13
END
